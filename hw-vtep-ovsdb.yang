module hw-vtep-ovsdb {
	
	namespace "urn:ietf:params:xml:ns:yang:hw-vtep-ovsdb";
    prefix "hwvtep";

    organization
    "Solo contributor"

    contact
    "Module Creator : Edward Henry
    	
    	Email : Networkn3rd@gmail.com
    	Skype handle : ehenry9
    	Twitter handle : @Networkn3rd"

    description
    	"This YANG module contains the information necessary to describe the OVS OVSDB schema implemented within hw-vtep"

    revision 2014-02-28 {
    	description 
    	"Original Revision";
    	reference
    	"Open vSwitch Manual : http://openvswitch.org/docs/vtep.5.pdf"
    }

/*** collection of table related field types within OVS OVSDB schema ***/

container manager-table {
	description "Contains configuration for a database connection to an Open vSwitch database (OVSDB) client"

	container core-features {

		container target {

			leaf target {
				type string;
				description
					"Connection method for managers";
			}
			leaf ssl-ip-port {
				type string;
				default "6632";
				description
				 "The speciﬁed SSL port (default: 6632) on the host at the given ip, which must be expressed as an IP address (not a DNS name). SSL key and certiﬁcate conﬁguration happens outside the database.";
			}
			leaf tcp-ip-port {
				type string;
				default "6632";
				description
				 "The speciﬁed TCP port (default: 6632) on the host at the given ip, which must be expressed as an IP address (not a DNS name).";
			}
			leaf pssl-port-ip {
				type string;
				default "6632";
				description
				 "Listens for SSL connections on the speciﬁed TCP port (default: 6632). If ip, which must
				  be expressed as an IP address (not a DNS name), is speciﬁed, then connections are
				  restricted to the speciﬁed local IP address.";
			}
			leaf ptcp-port-ip {
				type string;
				default "6632";
				description
				 "Listens for connections on the specified TCP port (default: 6632). If ip, which must be expressed as an IP address (not a DNS name), is specified, then connections are restricted to the specified local IP address."
			}
		}
			leaf max-backoff {
				type uint16{
					range "1000..65535";
					default "1000";
				}
				description
				 "Maximum number of milliseconds to wait between connection attempts. Default is implementation-specific.

				 According to the Open vSwitch Manual located at http://openvswitch.org/docs/vtep.5.pdf this should be a minimum of 1000";
			}

			feature inactivity-probe {
				description
				 "Maximum number of milliseconds of idle time on connection to the client before sending an inactivity probe message. If Open vSwitch does not communicate with the client for the specified number of seconds, it will send a probe. If a response is not received for the same additional amount of time, Open vSwitch assumes the connection has been broken and attempts to reconnect. Default is implementation-specific. A value of 0 disables inactivity probes.";
			}

			leaf inactivity_probe {
				if-feature inactivity-probe;
				type uint16;
				units "milliseconds";
				config false;
				description
				 ""
			}
		}

		}
	}
	
}

}
